MYAGENT-MIB DEFINITIONS ::= BEGIN

IMPORTS
    MODULE-IDENTITY, OBJECT-TYPE, Integer32, enterprises, NOTIFICATION-TYPE
        FROM SNMPv2-SMI
    DisplayString
        FROM SNMPv2-TC
    MODULE-COMPLIANCE, OBJECT-GROUP, NOTIFICATION-GROUP
        FROM SNMPv2-CONF;

myAgentMib MODULE-IDENTITY
    LAST-UPDATED "202511061200Z"
    ORGANIZATION "Zaragoza Network Management Research Group"
    CONTACT-INFO
        "Email: 740540.practicas@gmail.com"
    DESCRIPTION
        "Mini SNMP Agent MIB. Exposes manager info and CPU usage/threshold,
         and sends a notification if the threshold is exceeded."
    ::= { enterprises 28308 }

-- ==========================================================
--               MIB ROOTS
-- ==========================================================

cpuObjects       OBJECT IDENTIFIER ::= { myAgentMib 1 }
cpuNotifications OBJECT IDENTIFIER ::= { myAgentMib 2 }
cpuConformance   OBJECT IDENTIFIER ::= { myAgentMib 3 }

-- ==========================================================
--               OBJECT-TYPE DEFINITIONS
-- ==========================================================

manager OBJECT-TYPE
    SYNTAX      DisplayString (SIZE (1..255))
    MAX-ACCESS  read-write
    STATUS      current
    DESCRIPTION "Manager identifier that will receive notifications."
    ::= { cpuObjects 1 }

managerEmail OBJECT-TYPE
    SYNTAX      DisplayString (SIZE (3..255))
    MAX-ACCESS  read-write
    STATUS      current
    DESCRIPTION "Manager contact email."
    ::= { cpuObjects 2 }

cpuUsage OBJECT-TYPE
    SYNTAX      Integer32 (0..100)
    MAX-ACCESS  read-only
    STATUS      current
    DESCRIPTION "Current CPU usage in percent."
    ::= { cpuObjects 3 }

cpuThreshold OBJECT-TYPE
    SYNTAX      Integer32 (0..100)
    MAX-ACCESS  read-write
    STATUS      current
    DESCRIPTION "CPU threshold in percent that triggers a notification."
    ::= { cpuObjects 4 }

-- ==========================================================
--               NOTIFICATIONS
-- ==========================================================

cpuOverThresholdNotification NOTIFICATION-TYPE
    OBJECTS { cpuUsage, cpuThreshold, manager, managerEmail } -- en el enunciado pide cpuUsage, cpuThreshold, mangerEmail, DateAndTime
    STATUS  current
    DESCRIPTION
        "Sent when cpuUsage exceeds cpuThreshold."
    ::= { cpuNotifications 0 1 }   -- note the '0' for SMIv1/SMIv2 compatibility

-- ==========================================================
--               CONFORMANCE (optional but recommended)
-- ==========================================================

cpuObjectsGroup OBJECT-GROUP
    OBJECTS { manager, managerEmail, cpuUsage, cpuThreshold }
    STATUS  current
    DESCRIPTION "Group of scalar objects for the mini agent."
    ::= { cpuConformance 1 }

cpuNotificationsGroup NOTIFICATION-GROUP
    NOTIFICATIONS { cpuOverThresholdNotification }
    STATUS  current
    DESCRIPTION "Group of notifications for the mini agent."
    ::= { cpuConformance 2 }

cpuCompliance MODULE-COMPLIANCE
    STATUS  current
    DESCRIPTION "Minimal compliance for implementations of MYAGENT-MIB."
    MODULE
        MANDATORY-GROUPS { cpuObjectsGroup, cpuNotificationsGroup }
    ::= { cpuConformance 3 }

END
